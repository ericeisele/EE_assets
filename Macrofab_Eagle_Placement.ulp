if (board) board(B) {

    //File names for output.
    string fileName_XYRS = filesetext(B.name, ".XYRS");
    string fileName_PASTE = filesetext(B.name, ".PASTE");

    //Vars for finding max size of board.
    int Board_maxX = INT_MIN;
    int Board_minX = INT_MAX;
    int Board_maxY = INT_MIN;
    int Board_minY = INT_MAX;
	
	int temp_maxX = INT_MIN;
    int temp_minX = INT_MAX;
    int temp_maxY = INT_MIN;
    int temp_minY = INT_MAX;
	
	real w2 = 0;

    B.wires(W) 
    {
        if (W.layer == 20) 
        {
			w2 = W.width/2;
			if (W.x1-w2 < Board_minX) Board_minX = W.x1-w2;
			if (W.x2-w2 < Board_minX) Board_minX = W.x2-w2;
			if (W.x1+w2 > Board_maxX) Board_maxX = W.x1+w2;
			if (W.x2+w2 > Board_maxX) Board_maxX = W.x2+w2;
			if (W.y1-w2 < Board_minY) Board_minY = W.y1-w2;
			if (W.y2-w2 < Board_minY) Board_minY = W.y2-w2;
			if (W.y1+w2 > Board_maxY) Board_maxY = W.y1+w2;
			if (W.y2+w2 > Board_maxY) Board_maxY = W.y2+w2;
			
			if (W.arc)
			{
				if (W.arc.angle2 > 360)
				{
					temp_maxX = W.arc.xc + W.arc.radius + w2;
				}
				else if (((W.arc.angle1 <  90) && (W.arc.angle2 >  90)) || (W.arc.angle2 > 450))
				{
					temp_maxY = W.arc.yc + W.arc.radius + w2;
				}
				else if (((W.arc.angle1 < 180) && (W.arc.angle2 > 180)) || (W.arc.angle2 > 540))
				{
					temp_minX = W.arc.xc - W.arc.radius - w2;
				}
				else if (((W.arc.angle1 < 270) && (W.arc.angle2 > 270)) || (W.arc.angle2 > 630))
				{
					temp_minY = W.arc.yc - W.arc.radius - w2;
				}
				
				Board_minX = min(Board_minX, temp_minX);
				Board_maxX = max(Board_maxX, temp_maxX);
				Board_minY = min(Board_minY, temp_minY);
				Board_maxY = max(Board_maxY, temp_maxY);
			}		
        }
    }
	//Check for circle dimension layer
	B.circles(C) 
	{
		if(C.layer == 20)
		{
			w2 = C.width / 2;
			temp_maxX = C.x + C.radius + w2;
			temp_minX = C.x - C.radius - w2;
			temp_maxY = C.y + C.radius + w2;
			temp_minY = C.y - C.radius - w2;
			
			Board_minX = min(Board_minX, temp_minX);
			Board_maxX = max(Board_maxX, temp_maxX);
			Board_minY = min(Board_minY, temp_minY);
			Board_maxY = max(Board_maxY, temp_maxY);
		}
	}
	//Check parts
	B.elements(T)
	{
		T.package.wires(Y)
		{
			if (Y.layer == 20) 
			{
				w2 = Y.width/2;
				if (Y.x1-w2 < Board_minX) Board_minX = Y.x1-w2;
				if (Y.x2-w2 < Board_minX) Board_minX = Y.x2-w2;
				if (Y.x1+w2 > Board_maxX) Board_maxX = Y.x1+w2;
				if (Y.x2+w2 > Board_maxX) Board_maxX = Y.x2+w2;
				if (Y.y1-w2 < Board_minY) Board_minY = Y.y1-w2;
				if (Y.y2-w2 < Board_minY) Board_minY = Y.y2-w2;
				if (Y.y1+w2 > Board_maxY) Board_maxY = Y.y1+w2;
				if (Y.y2+w2 > Board_maxY) Board_maxY = Y.y2+w2;
				
				if (Y.arc)
				{
					if (Y.arc.angle2 > 360)
					{
						temp_maxX = Y.arc.xc + Y.arc.radius + w2;
					}
					else if (((Y.arc.angle1 <  90) && (Y.arc.angle2 >  90)) || (Y.arc.angle2 > 450))
					{
						temp_maxY = Y.arc.yc + Y.arc.radius + w2;
					}
					else if (((Y.arc.angle1 < 180) && (Y.arc.angle2 > 180)) || (Y.arc.angle2 > 540))
					{
						temp_minX = Y.arc.xc - Y.arc.radius - w2;
					}
					else if (((Y.arc.angle1 < 270) && (Y.arc.angle2 > 270)) || (Y.arc.angle2 > 630))
					{
						temp_minY = Y.arc.yc - Y.arc.radius - w2;
					}
					
					Board_minX = min(Board_minX, temp_minX);
					Board_maxX = max(Board_maxX, temp_maxX);
					Board_minY = min(Board_minY, temp_minY);
					Board_maxY = max(Board_maxY, temp_maxY);
				}		
			}
		}
		T.package.circles(P)
		{
			if(P.layer == 20)
			{
				w2 = P.width / 2;
				temp_maxX = P.x + P.radius + w2;
				temp_minX = P.x - P.radius - w2;
				temp_maxY = P.y + P.radius + w2;
				temp_minY = P.y - P.radius - w2;
				
				Board_minX = min(Board_minX, temp_minX);
				Board_maxX = max(Board_maxX, temp_maxX);
				Board_minY = min(Board_minY, temp_minY);
				Board_maxY = max(Board_maxY, temp_maxY);
			}
		}
		
	}
  
    //Build XYRS Data
    output(fileName_XYRS) 
    {
        //Build File Header
        printf("#MacroFab, INC. XYRS data for %s.\n",B.name);
		printf("#Board Size is %f x %f.\n#\n",u2mil(Board_maxX - Board_minX),u2mil(Board_maxY - Board_minY));
        printf("#Placement Data:\n");
        printf("#Designator\tX-Loc\tY-Loc\tRotation\tSide\tType\tX-Size\tY-Size\tValue\tFootprint\n");
        //Part level
        B.elements(E) if (E.populate) 
        {
            int type = 0;
            
            int x_cen = 0;
            int y_cen = 0;
            
            int side = 0;
                    
            int xmax = INT_MIN;
            int xmin = INT_MAX;
            int ymax = INT_MIN;
            int ymin = INT_MAX;
            
            int footprint_xmax = INT_MIN;
            int footprint_xmin = INT_MAX;
            int footprint_ymax = INT_MIN;
            int footprint_ymin = INT_MAX;
            
            int rot_x = 1;
            int rot_y = 1;
            
            int smd_cnt = 0;
            int pth_cnt = 0;

			real p_angle = E.angle;
            
            E.package.contacts(C) 
            {           
                //Find max and min X-Y
                
                if (C.x > xmax) xmax = C.x;
                if (C.y > ymax) ymax = C.y;
                if (C.x < xmin) xmin = C.x;
                if (C.y < ymin) ymin = C.y;
                    
                if (C.smd) 
                {
                    smd_cnt++;
                }
                else
                {
                    pth_cnt++;
                }
                
                if(E.mirror == 0)
                {
                    side = 1;
                }
                else
                {
                    side = 2;
                }
            }
            
            //SMD or PTH part?
            if(smd_cnt >= pth_cnt)
            {
                type = 1;
            }
            else
            {
                type = 2; 
            }
            
            //Find center of package
            x_cen = ((xmin + xmax)/2);
            y_cen = ((ymin + ymax)/2);
                
            E.package.contacts(C) 
            {
                //Find package size for SMT
                if (C.smd) 
                {               
                    if(C.smd.angle == 0 || C.smd.angle == 180)
                    {
                        if ((C.x + (C.smd.dx / 2)) > footprint_xmax) footprint_xmax = (C.x + (C.smd.dx / 2));
                        if ((C.y + (C.smd.dy / 2)) > footprint_ymax) footprint_ymax = (C.y + (C.smd.dy / 2));
                        if ((C.x - (C.smd.dx / 2)) < footprint_xmin) footprint_xmin = (C.x - (C.smd.dx / 2));
                        if ((C.y - (C.smd.dy / 2)) < footprint_ymin) footprint_ymin = (C.y - (C.smd.dy / 2));
                    }
                    else if(C.smd.angle ==  90 || C.smd.angle == 270)
                    {
                        if ((C.x + (C.smd.dy / 2)) > footprint_xmax) footprint_xmax = (C.x + (C.smd.dy / 2));
                        if ((C.y + (C.smd.dx / 2)) > footprint_ymax) footprint_ymax = (C.y + (C.smd.dx / 2));
                        if ((C.x - (C.smd.dy / 2)) < footprint_xmin) footprint_xmin = (C.x - (C.smd.dy / 2));
                        if ((C.y - (C.smd.dx / 2)) < footprint_ymin) footprint_ymin = (C.y - (C.smd.dx / 2));
                    }
                    //Weird angle parts
                    else
                    {
                        rot_x = int(x_cen + (C.x-x_cen)*cos((p_angle * PI)/180) - (C.y-y_cen)*sin(-(p_angle * PI)/180));
                        rot_y = y_cen + (C.x-x_cen)*sin(-(p_angle * PI)/180) + (C.y-y_cen)*cos((p_angle * PI)/180);
                        
                        if((abs(C.smd.angle - p_angle)) == 0 || (abs(C.smd.angle - p_angle)) == 180)
                        {
                            if ((rot_x + (C.smd.dx / 2)) > footprint_xmax) footprint_xmax = (rot_x + (C.smd.dx / 2));
                            if ((rot_y + (C.smd.dy / 2)) > footprint_ymax) footprint_ymax = (rot_y + (C.smd.dy / 2));
                            if ((rot_x - (C.smd.dx / 2)) < footprint_xmin) footprint_xmin = (rot_x - (C.smd.dx / 2));
                            if ((rot_y - (C.smd.dy / 2)) < footprint_ymin) footprint_ymin = (rot_y - (C.smd.dy / 2));
                        }
                        else if((abs(C.smd.angle - p_angle)) ==  90 || (abs(C.smd.angle - p_angle)) == 270)
                        {
                            if ((rot_x + (C.smd.dy / 2)) > footprint_xmax) footprint_xmax = (rot_x + (C.smd.dy / 2));
                            if ((rot_y + (C.smd.dx / 2)) > footprint_ymax) footprint_ymax = (rot_y + (C.smd.dx / 2));
                            if ((rot_x - (C.smd.dy / 2)) < footprint_xmin) footprint_xmin = (rot_x - (C.smd.dy / 2));
                            if ((rot_y - (C.smd.dx / 2)) < footprint_ymin) footprint_ymin = (rot_y - (C.smd.dx / 2));
                        }
                        //Should Never get here
                        else
                        {
                            printf("\nERROR:\tC.smd.angle = %5.2f\tp_angle = %5.2f\n", C.smd.angle, p_angle);
                        }
                    }   
                }   
                //Find package size for PTH
                else
                {               
                    if(C.pad.angle == 0 || C.pad.angle == 180)
                    {
                        if ((C.x + (C.pad.drill / 2)) > footprint_xmax) footprint_xmax = (C.x + (C.pad.drill / 2));
                        if ((C.y + (C.pad.drill / 2)) > footprint_ymax) footprint_ymax = (C.y + (C.pad.drill / 2));
                        if ((C.x - (C.pad.drill / 2)) < footprint_xmin) footprint_xmin = (C.x - (C.pad.drill / 2));
                        if ((C.y - (C.pad.drill / 2)) < footprint_ymin) footprint_ymin = (C.y - (C.pad.drill / 2));
                    }
                    else if(C.pad.angle ==  90 || C.pad.angle == 270)
                    {
                        if ((C.x + (C.pad.drill / 2)) > footprint_xmax) footprint_xmax = (C.x + (C.pad.drill / 2));
                        if ((C.y + (C.pad.drill / 2)) > footprint_ymax) footprint_ymax = (C.y + (C.pad.drill / 2));
                        if ((C.x - (C.pad.drill / 2)) < footprint_xmin) footprint_xmin = (C.x - (C.pad.drill / 2));
                        if ((C.y - (C.pad.drill / 2)) < footprint_ymin) footprint_ymin = (C.y - (C.pad.drill / 2));
                    }
                    //Weird angle parts
                    else
                    {
                        rot_x = int(x_cen + (C.x-x_cen)*cos((p_angle * PI)/180) - (C.y-y_cen)*sin(-(p_angle * PI)/180));
                        rot_y = y_cen + (C.x-x_cen)*sin(-(p_angle * PI)/180) + (C.y-y_cen)*cos((p_angle * PI)/180);
                        
                        if((abs(C.pad.angle - p_angle)) == 0 || (abs(C.pad.angle - p_angle)) == 180)
                        {
                            if ((rot_x + (C.pad.drill / 2)) > footprint_xmax) footprint_xmax = (rot_x + (C.pad.drill / 2));
                            if ((rot_y + (C.pad.drill / 2)) > footprint_ymax) footprint_ymax = (rot_y + (C.pad.drill / 2));
                            if ((rot_x - (C.pad.drill / 2)) < footprint_xmin) footprint_xmin = (rot_x - (C.pad.drill / 2));
                            if ((rot_y - (C.pad.drill / 2)) < footprint_ymin) footprint_ymin = (rot_y - (C.pad.drill / 2));
                        }
                        else if((abs(C.pad.angle - p_angle)) ==  90 || (abs(C.pad.angle - p_angle)) == 270)
                        {
                            if ((rot_x + (C.pad.drill / 2)) > footprint_xmax) footprint_xmax = (rot_x + (C.pad.drill / 2));
                            if ((rot_y + (C.pad.drill / 2)) > footprint_ymax) footprint_ymax = (rot_y + (C.pad.drill / 2));
                            if ((rot_x - (C.pad.drill / 2)) < footprint_xmin) footprint_xmin = (rot_x - (C.pad.drill / 2));
                            if ((rot_y - (C.pad.drill / 2)) < footprint_ymin) footprint_ymin = (rot_y - (C.pad.drill / 2));
                        }
                        //Should Never get here
                        else
                        {
                            printf("\nERROR:\tC.pad.angle = %5.2f\tp_angle = %5.2f\n", C.pad.angle, p_angle);
                        }
                    }   
                }
            }
			if((p_angle == 90) || (p_angle == 270))
			{
				printf("%s\t%5.2f\t%5.2f\t%.0f\t%d\t%d\t%5.2f\t%5.2f\t%s\t%s\n",E.name, u2mil(x_cen-Board_minX), u2mil(y_cen-Board_minY),E.angle, side, type, u2mil(footprint_ymax - footprint_ymin), u2mil(footprint_xmax - footprint_xmin), E.attribute["MFG#"], E.package.name);
			}
			else
			{
				printf("%s\t%5.2f\t%5.2f\t%.0f\t%d\t%d\t%5.2f\t%5.2f\t%s\t%s\n",E.name, u2mil(x_cen-Board_minX), u2mil(y_cen-Board_minY),E.angle, side, type, u2mil(footprint_xmax - footprint_xmin), u2mil(footprint_ymax - footprint_ymin), E.attribute["MFG#"], E.package.name);			
			}
        }
    }
    
    //Build Paste Top Files
    output(fileName_PASTE)
    {
        //Build File Header
        printf("#MacroFab, INC. PASTE data for %s.\n#\n",B.name);
        printf("#PASTE Data:\n");
        printf("#Designator\tX-Loc\tY-Loc\tSide\tType\tX-Size\tY-Size\n");
        
        B.elements(E) if (E.populate)
        {
            E.package.contacts(C) 
            {
                int type = 0;
                int side = 0;
                
                int x_cen = C.x;
                int y_cen = C.y;
            
                int x_size = 0;
                int y_size = 0;
                
                if (C.smd) 
                {
                    type = 1;
                    x_size = C.smd.dx;
                    y_size = C.smd.dy;
                }
                else
                {
                    type = 2;
                    x_size = C.pad.drill;
                    y_size = C.pad.drill;
                }
                
                if(E.mirror == 0)
                {
                    side = 1;
                }
                else
                {
                    side = 2;
                }
                                            
                printf("%s\t%5.2f\t%5.2f\t%d\t%d\t%5.2f\t%5.2f\n", E.name, u2mil(x_cen-Board_minX), u2mil(y_cen-Board_minY), side, type, u2mil(x_size), u2mil(y_size));
            }
        }
    }   

}
